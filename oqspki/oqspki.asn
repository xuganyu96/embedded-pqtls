AlgorithmIdentifier ::= SEQUENCE {
    oid OBJECT IDENTIFIER,
    parameters ANY DEFINED BY oid OPTIONAL
}

PrivateKeyDER ::= SEQUENCE {
    version INTEGER,
    algorithm AlgorithmIdentifier,
    sk OCTET STRING
}

PublicKeyDER ::= SEQUENCE {
    algorithm AlgorithmIdentifier,
    pk BIT STRING
}
